-- Module UL-AttributeModule (X.227:03/1999)
-- See also ITU-T X.287 (03/1999)
-- See also the index of all ASN.1 assignments needed in this document

UL-AttributeModule {joint-iso-itu-t ms(9) smi(3) part8(8) asn1Module(2) 0}
DEFINITIONS ::=
BEGIN

--EXPORTS everything
IMPORTS
  RelativeDistinguishedName
    FROM InformationFramework {joint-iso-itu-t ds(5) modules(1)
      informationFramework(1) 3}
  AP-title, Application-context-name, AE-invocation-identifier,
    AP-invocation-identifier, AE-qualifier, AE-title, ACSE-requirements
    FROM ACSE-1 {joint-iso-itu-t association-control(2) modules(0) apdus(0)
      version1(1)}
  Presentation-requirements, Presentation-selector, Context-list,
    Abstract-syntax-name, Transfer-syntax-name
    FROM ISO8823-PRESENTATION
  ObjectInstances
    FROM CMIP-1 {joint-iso-itu-t ms(9) cmip(1) modules(0) protocol(3)};

--value references
ulMObjectClass OBJECT IDENTIFIER ::=
  {joint-iso-itu-t ms(9) smi(3) part8(8) managedObjectClass(3)}

END -- of UL-AttributeModule

-- Generated by Asnp, the ASN.1 pretty-printer of France Telecom R&D
